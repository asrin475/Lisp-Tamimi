(defun insrt (s l n) (strcat (substr s 1 (1- n)) l (substr s (1+ n))))
(defun cgs (s os ns / sl osl nsl st si)
     (setq osl (strlen os) nsl (strlen ns) si 1)
     (while (= osl (setq sl (strlen (setq st (substr s si osl)))))
        (if (= os st)
            (setq s (strcat (substr s 1 (1- si)) ns (substr s (+ si osl)))
                  si (+ si nsl))
            (setq si (1+ si)))) (eval s))
(defun chltr (s ltr1 ltr2 ltr3 ltr4 L L- -L- -L / cnt sltr prvl nxtl tn)
(setq cnt 1)
 (while (= 1 (strlen (setq sltr (substr s cnt 1))))
  (if (or (= ltr1 sltr) (= ltr2 sltr) (= ltr3 sltr) (= ltr4 sltr)) 
   (progn         
         (if (= 1 cnt) (setq prvl "") (setq prvl (substr s (1- cnt) 1)))
         (setq nxtl (substr s (1+ cnt) 1))
     (if (or (= prvl "" ) (= prvl " ") (= prvl "H") (= prvl "h") (= prvl "X")
             (= prvl "x") (= prvl "N") (= prvl "n") (= prvl "]") (= prvl "`")
             (= prvl "V") (= prvl "v") (= prvl ">") (= prvl ",") (= prvl "C")
             (= prvl "c") (= prvl "B") (= prvl "b") (= prvl "’") (= prvl "‘")
             (= prvl "¥") (= prvl "¤") (= prvl "<") (= prvl ")") (= prvl "(")
             (= prvl "!") (= prvl "?") (= prvl "%") (= nxlt "ð"))
                 (if (or (= nxtl "" ) (= nxtl " ") (= nxlt "<")
                         (= nxtl ")") (= nxtl "(") (= nxlt "!")
                         (= nxlt "?") (= nxlt "%") (= nxlt "ð"))
                     (setq s (insrt s  L  cnt)) (setq s (insrt s  L- cnt)))
                 (if (or (= nxtl "" ) (= nxtl " ") (= nxlt "<")
                         (= nxtl ")") (= nxtl "(") (= nxlt "!")
                         (= nxlt "?") (= nxlt "%") (= nxlt "ð"))
                     (setq s (insrt s -L  cnt)) (setq s (insrt s -L- cnt))))))
  (setq cnt (1+ cnt))) (eval s))
(defun c:ct (/ s e os)
  (setq e (entget (car (entsel "\nSelect text: "))))
  (setq s (cdr (setq os (assoc 1 e))))
  (setq s (chltr s "H" "H" "h" "h" "H" "H" "h" "h"))
  (setq s (chltr s "X" "X" "x" "x" "î" "X" "î" "x"))
  (setq s (chltr s "N" "N" "n" "n" "N" "N" "n" "n"))
  (setq s (chltr s "F" "f" "f" "F" "F" "f" "f" "F"))
  (setq s (chltr s "J" "j" "j" "J" "J" "j" "j" "J"))
  (setq s (chltr s "E" "e" "e" "E" "E" "e" "e" "E"))
  ;(setq s (chltr s "[" "{" "{" "%%176" "[" "{" "{" "%%176"))
  ;(setq s (chltr s "P" "p" "p" "%%177" "P" "p" "p" "%%177"))
  (setq s (chltr s "[" "{" "{" "%%176" "[" "{" "{" "{"))
  (setq s (chltr s "P" "p" "p" "%%177" "P" "p" "p" "P")) ; because the extra character turns into a + mark after the file is opened
  (setq s (chltr s "O" "o" "o" "²" "O" "o" "o" "²"))
  (setq s (chltr s "S" "s" "s" "S" "S" "s" "s" "S"))
  (setq s (chltr s "A" "a" "a" "A" "A" "a" "a" "A"))
  (setq s (chltr s "W" "w" "w" "W" "W" "w" "w" "W"))
  (setq s (chltr s "Q" "q" "q" "Q" "Q" "q" "q" "Q"))
  (setq s (chltr s "U" "u" "–" "š" "U" "u" "–" "š"))
  (setq s (chltr s "Y" "y" "˜" "�" "Y" "y" "˜" "�"))
  (setq s (chltr s "T" "t" "œ" "Ÿ" "T" "t" "œ" "Ÿ"))
  (setq s (chltr s "R" "r" "ž" "R" "R" "r" "ž" "R"))
  (setq s (chltr s ";" ":" "Ê" ";" ";" ":" "Ê" ";"))
  (setq s (chltr s "§" "§" "§" "§" "§" "§" "§" ";"))
  (setq s (chltr s "G" "g" "g" "G" "G" "g" "g" "G"))
  (setq s (chltr s "L" "l" "l" "â" "L" "l" "l" "â"))
  (setq s (chltr s "K" "k" "k" "K" "K" "k" "k" "K"))
  (setq s (chltr s "I" "i" "Œ" "�" "I" "i" "Œ" "�"))
  (setq s (chltr s "D" "d" "d" "å" "D" "d" "d" "å"))
  (setq s (chltr s "Z" "z" "z" "ë" "Z" "z" "z" "ë"))
  (setq s (cgs s "gh" "b")) (setq s (cgs s "gx" "’"))
  (setq s (cgs s "gn" "¥")) (setq s (cgs s "g¦" "½"))
  (setq s (chltr s "B" "B" "b" "b" "B" "B" "b" "b"))
  (setq s (chltr s "’" "’" "‘" "‘" "’" "’" "‘" "‘"))
  (setq s (chltr s "¥" "¥" "¤" "¤" "¥" "¥" "¤" "¤"))
  (setq s (chltr s "M" "M" "m" "m" "M" "j" "j" "m"))
  (setq e (subst (cons 1 s) os e))
  (entmod e)
(princ)
)
